(DEFUN C:KIRIS_D ()
  (COMMAND "UNDO" "GROUP")
  (SETQ CURRENT_OSM (GETVAR "OSMODE"))
  (SETVAR "OSMODE" 0)
  (SETVAR "CMDECHO" 0)
  (SETVAR "BLIPMODE" 0)  
  (vl-load-com)
  (COMMAND-S "_ZOOM" "_E")
  (SETQ ALLSEC_0 (SSGET "X" (LIST (CONS -4 "<NOT") (CONS 62 4) (CONS -4 "NOT>"))))
  (COMMAND-S "-OVERKILL" ALLSEC_0 "" "")
  (SETQ ALLSEC_1 (SSGET "X" (LIST (CONS 0 "LINE"))))
  (SETQ ALLSEC_1Y (SSADD))
  (SETQ SAYAC 0)
  (SETQ ALLSEC_1_A (SSLENGTH ALLSEC_1))
  (REPEAT ALLSEC_1_A
    (IF (< (DISTANCE (CDR (ASSOC 10 (ENTGET (SSNAME ALLSEC_1 SAYAC)))) (CDR (ASSOC 11 (ENTGET (SSNAME ALLSEC_1 SAYAC))))) 0.001)
      (SETQ ALLSEC_1Y (SSADD (SSNAME ALLSEC_1 SAYAC) ALLSEC_1Y )));IF
    (SETQ SAYAC (1+ SAYAC))
  );REPEAT
  (COMMAND-S "_ERASE" ALLSEC_1Y "")
  (SETQ ALLSEC_1 (SSGET "X" (LIST (CONS 0 "TEXT"))))
  (SETQ ALLSEC_1_A (SSLENGTH ALLSEC_1))
  (SETQ SAYAC 0)
  (REPEAT ALLSEC_1_A
    (ENTMOD (SUBST (CONS 41 1.0) (CONS 41 (CDR (ASSOC 41 (ENTGET (SSNAME ALLSEC_1 SAYAC))))) (ENTGET (SSNAME ALLSEC_1 SAYAC))))
    (SETQ SAYAC (1+ SAYAC))
  );REPEAT
  (COMMAND-S "_ZOOM" "_E")
  (COMMAND-S "_LTSCALE" 0.5 "")
  (COMMAND-S "_.UNITS" "" "" "" "" "" "N")
  ;OLCEK KONTROL
  (IF (/= (SSGET "X" (LIST (CONS 0 "CIRCLE") (CONS 8 "AXIS3"))) NIL)
    (PROGN
      (SETQ AKS_HALKA (SSGET "X" (LIST (CONS 0 "CIRCLE") (CONS 8 "AXIS3"))))
      (IF (< (CDR (ASSOC 40 (ENTGET (SSNAME AKS_HALKA 0)))) 0.01)
	(COMMAND-S "_SCALE" (SSGET "X") "" '(0 0) 5000));IF
    );PROGN
  );IF
  ;OLCEK KONTROL
  (COMMAND-S "_ZOOM" "_E")
  ;LAYER-STYLE KONTROL
  (COMMAND-S "_CHPROP" (SSGET "X") "" "C" "BYLAYER" "")
  (COMMAND-S "_CHPROP" (SSGET "X") "" "LT" "BYLAYER" "")
  (IF (= (TBLSEARCH "STYLE" "YAZI (BEYKENT)") nil)
    (vla-setfont (vla-add (vla-get-textstyles (vla-get-activedocument (vlax-get-acad-object))) "YAZI (BEYKENT)") "BAHNSCHRIFT LIGHT CONDENSED" :vlax-False :vlax-False 0 32));IF
  (IF (= (TBLSEARCH "STYLE" "KOT (BEYKENT)") nil)
    (vla-setfont (vla-add (vla-get-textstyles (vla-get-activedocument (vlax-get-acad-object))) "KOT (BEYKENT)") "BAHNSCHRIFT LIGHT CONDENSED" :vlax-False :vlax-False 0 32));IF
  (IF (= (TBLSEARCH "STYLE" "OLCU (BEYKENT)") nil)
    (vla-setfont (vla-add (vla-get-textstyles (vla-get-activedocument (vlax-get-acad-object))) "OLCU (BEYKENT)") "BAHNSCHRIFT LIGHT CONDENSED" :vlax-False :vlax-False 0 32));IF
  ;LAYER-STYLE KONTROL
  ;AKS BALONU
  (IF (/= (SSGET "X" (LIST (CONS 0 "CIRCLE") (CONS 8 "AXIS3"))) NIL)
    (PROGN
      (SETQ AXIS3 (SSGET "X" (LIST (CONS 0 "CIRCLE") (CONS 8 "AXIS3"))))
      (SETQ AXIS3_A (SSLENGTH AXIS3))
      (SETQ SAYAC 0)
      (REPEAT AXIS3_A
	(ENTMOD (SUBST (CONS 8 "AKS BALONU (BEYKENT)") (CONS 8 "AXIS3") (ENTGET (SSNAME AXIS3 SAYAC))))
	(SETQ SAYAC (1+ SAYAC))
      );REPEAT
      (COMMAND-S "_LAYER" "S" "AKS BALONU (BEYKENT)" "C" 7 "AKS BALONU (BEYKENT)" "LW" 0.2 "AKS BALONU (BEYKENT)" "")
    );PROGN
  );IF
  ;AKS BALONU
  ;AKS CIZGISI
  (IF (/= (SSGET "X" (LIST (CONS 0 "LINE") (CONS 8 "AXIS2"))) NIL)
    (PROGN
      (SETQ AXIS2 (SSGET "X" (LIST (CONS 0 "LINE") (CONS 8 "AXIS2"))))
      (SETQ AXIS2_A (SSLENGTH AXIS2))
      (SETQ SAYAC 0)
      (REPEAT AXIS2_A
	(ENTMOD (SUBST (CONS 8 "AKS CIZGISI (BEYKENT)") (CONS 8 "AXIS2") (ENTGET (SSNAME AXIS2 SAYAC))))
	(COMMAND-S "_DRAWORDER" (SSNAME AXIS2 SAYAC) "" "")
	(SETQ SAYAC (1+ SAYAC))
      );REPEAT
      (COMMAND-S "_LAYER" "S" "AKS CIZGISI (BEYKENT)" "C" 252 "AKS CIZGISI (BEYKENT)" "LW" 0.2 "AKS CIZGISI (BEYKENT)" "LT" "DASHED" "AKS CIZGISI (BEYKENT)" "")
    );PROGN
  );IF
  ;AKS CIZGISI
  ;AKS NO
  (IF (/= (SSGET "X" (LIST (CONS 0 "TEXT") (CONS 8 "AXIS4"))) NIL)
    (PROGN
      (SETQ AXIS4 (SSGET "X" (LIST (CONS 0 "TEXT") (CONS 8 "AXIS4"))))
      (SETQ AXIS4_A (SSLENGTH AXIS4))
      (SETQ SAYAC 0)
      (REPEAT AXIS4_A
	(ENTMOD (SUBST (CONS 8 "AKS NO (BEYKENT)") (CONS 8 "AXIS4") (ENTGET (SSNAME AXIS4 SAYAC))))
	(ENTMOD (SUBST (CONS 7 "YAZI (BEYKENT)") (CONS 7 "stastyle") (ENTGET (SSNAME AXIS4 SAYAC))))
	(SETQ SAYAC (1+ SAYAC))
      );REPEAT
      (COMMAND-S "_LAYER" "S" "AKS NO (BEYKENT)" "C" 3 "AKS NO (BEYKENT)" "LW" 0.2 "AKS NO (BEYKENT)" "")
    );PROGN
    );IF
  ;AKS NO
  ;KIRIS YAZI
  (IF (/= (SSGET "X" (LIST (CONS 0 "TEXT") (CONS 40 25) (CONS 8 "BEAM4"))) NIL)
    (PROGN
      (SETQ BEAM4 (SSGET "X" (LIST (CONS 0 "TEXT") (CONS 40 25) (CONS 8 "BEAM4"))))
      (SETQ BEAM4_A (SSLENGTH BEAM4))
      (SETQ SAYAC 0)
      (REPEAT BEAM4_A
	(ENTMOD (SUBST (CONS 8 "KIRIS ISMI (BEYKENT)") (CONS 8 "BEAM4") (ENTGET (SSNAME BEAM4 SAYAC))))	
	(ENTMOD (SUBST (CONS 40 20) (CONS 40 25) (ENTGET (SSNAME BEAM4 SAYAC))))
	(ENTMOD (SUBST (CONS 7 "YAZI (BEYKENT)") (CONS 7 "stastyle") (ENTGET (SSNAME BEAM4 SAYAC))))
	(SETQ SAYAC (1+ SAYAC))
      );REPEAT
      (COMMAND-S "_LAYER" "S" "KIRIS ISMI (BEYKENT)" "C" 40 "KIRIS ISMI (BEYKENT)" "LW" 0.2 "KIRIS ISMI (BEYKENT)" "")
    );PROGN
    );IF
  ;KIRIS YAZI
  ;KIRIS CIZGILERI
  (IF (/= (SSGET "X" (LIST (CONS 0 "LINE") (CONS 8 "BEAM3"))) NIL)
    (PROGN
      (SETQ BEAM3 (SSGET "X" (LIST (CONS 0 "LINE") (CONS 8 "BEAM3"))))
      (SETQ BEAM3_A (SSLENGTH BEAM3))
      (SETQ SAYAC 0)
      (REPEAT BEAM3_A
	(ENTMOD (SUBST (CONS 8 "KIRIS (BEYKENT)") (CONS 8 "BEAM3") (ENTGET (SSNAME BEAM3 SAYAC))))
	(SETQ SAYAC (1+ SAYAC))
      );REPEAT
      (COMMAND-S "_LAYER" "S" "KIRIS (BEYKENT)" "C" 2 "KIRIS (BEYKENT)" "LW" 0.3 "KIRIS (BEYKENT)" "")
    );PROGN
  );IF
  ;KIRIS CIZGILERI
  ;KOT CIZGILERI VE YAZILARI
  (IF (/= (SSGET "X" (LIST (CONS 0 "TEXT")(CONS 1 "*`.*")(CONS 8 "DETAIL3"))) NIL)
    (PROGN
      (SETQ DETAIL3 (SSGET "X" (LIST (CONS 0 "TEXT")(CONS 1 "*`.*")(CONS 8 "DETAIL3"))))
      (SETQ DETAIL3_A (SSLENGTH DETAIL3))
      (SETQ SAYAC 0)
      (REPEAT DETAIL3_A
	(COMMAND-S "_ERASE" (SSGET "_W" (MAPCAR '+ '(-70.0 -55.0 0.0) (CDR (ASSOC 10 (ENTGET (SSNAME DETAIL3 SAYAC))))) (MAPCAR '+ '(70.0 0.0 0.0) (CDR (ASSOC 10 (ENTGET (SSNAME DETAIL3 SAYAC))))) (LIST (CONS 0 "LINE") (CONS 8 "DETAIL2"))) "" )
	(ENTMOD (SUBST (CONS 10 (LIST (CAR (CDR (ASSOC 10 (ENTGET (SSNAME DETAIL3 SAYAC))))) (+ (CADR (CDR (ASSOC 10 (ENTGET (SSNAME DETAIL3 SAYAC))))) -35.0) (CADDR (CDR (ASSOC 10 (ENTGET (SSNAME DETAIL3 SAYAC))))))) (CONS 10 (CDR (ASSOC 10 (ENTGET (SSNAME DETAIL3 SAYAC))))) (ENTGET (SSNAME DETAIL3 SAYAC))))
	(ENTMOD (SUBST (CONS 8 "KOT YAZI (BEYKENT)") (CONS 8 (CDR(ASSOC 8(ENTGET(SSNAME DETAIL3 SAYAC))))) (ENTGET(SSNAME DETAIL3 SAYAC))))
	(ENTMOD (SUBST (CONS 7 "KOT (BEYKENT)") (CONS 7 (CDR(ASSOC 7(ENTGET(SSNAME DETAIL3 SAYAC))))) (ENTGET (SSNAME DETAIL3 SAYAC))))
	(ENTMOD (SUBST (CONS 40 10) (CONS 40 (CDR(ASSOC 40(ENTGET(SSNAME DETAIL3 SAYAC))))) (ENTGET (SSNAME DETAIL3 SAYAC))))
	(SETQ SAYAC (1+ SAYAC))
      );REPEAT
      (COMMAND-S "_LAYER" "S" "KOT YAZI (BEYKENT)" "C" 7 "KOT YAZI (BEYKENT)" "LW" 0.2 "KOT YAZI (BEYKENT)" "")
    );PROGN
  );IF
  ;KOT CIZGILERI VE YAZILARI
  ;KOLON YAZI
  (IF (/= (SSGET "X" (LIST (CONS 0 "TEXT")(CONS 40 12.5)(CONS 8 "PENC3"))) NIL)
    (PROGN
      (SETQ PENC3 (SSGET "X" (LIST (CONS 0 "TEXT")(CONS 40 12.5)(CONS 8 "PENC3"))))
      (SETQ PENC3_A (SSLENGTH PENC3))
      (SETQ SAYAC 0)
      (REPEAT PENC3_A
	(ENTMOD (SUBST (CONS 8 "KOLON ISMI (BEYKENT)") (CONS 8 (CDR(ASSOC 8(ENTGET(SSNAME PENC3 SAYAC))))) (ENTGET (SSNAME PENC3 SAYAC))))	
	(ENTMOD (SUBST (CONS 7 "YAZI (BEYKENT)") (CONS 7 (CDR(ASSOC 7(ENTGET(SSNAME PENC3 SAYAC))))) (ENTGET (SSNAME PENC3 SAYAC))))
	(SETQ SAYAC (1+ SAYAC))
      );REPEAT
      (COMMAND-S "_LAYER" "S" "KOLON ISMI (BEYKENT)" "C" 91 "KOLON ISMI (BEYKENT)" "LW" 0.2 "KOLON ISMI (BEYKENT)" "")
    );PROGN
  );IF
  ;KOLON YAZI
  ;DONATI OKLARI VE KESIT YAZISI
  (IF (/= (SSGET "X" (LIST (CONS 0 "TEXT")(CONS 1 "*KESITI*")(CONS 8 "DETAIL4"))) NIL)
    (PROGN
      (SETQ DETAIL4 (SSGET "X" (LIST (CONS 0 "TEXT")(CONS 1 "*KESITI*")(CONS 8 "DETAIL4"))))
      (SETQ DETAIL4_A (SSLENGTH DETAIL4))
      (SETQ SAYAC 0)
      (REPEAT DETAIL4_A
	(SETQ CIZGI_ALT NIL)
	(SETQ CIZGI_UST NIL)
	(ENTMOD (SUBST (CONS 8 "KESIT ISMI (BEYKENT)") (CONS 8 (CDR(ASSOC 8(ENTGET(SSNAME DETAIL4 SAYAC))))) (ENTGET (SSNAME DETAIL4 SAYAC))))
	(ENTMOD (SUBST (CONS 40 15) (CONS 40 (CDR(ASSOC 40(ENTGET(SSNAME DETAIL4 SAYAC))))) (ENTGET (SSNAME DETAIL4 SAYAC))))
	(ENTMOD (SUBST (CONS 7 "YAZI (BEYKENT)") (CONS 7 (CDR(ASSOC 7(ENTGET(SSNAME DETAIL4 SAYAC))))) (ENTGET (SSNAME DETAIL4 SAYAC))))
	(SETQ REF_NOK1 (MAPCAR '+ '(40.0 60.0 0.0)(CDR(ASSOC 10(ENTGET(SSNAME DETAIL4 SAYAC))))))
	(SETQ REF_NOK2 (MAPCAR '+ '(0.0 30.0 0.0)REF_NOK1))	
	(SETQ CIZGI_ALT (SSGET "_F" (LIST REF_NOK1 REF_NOK2)(LIST (CONS 0 "LINE") (CONS 8 "DETAIL3"))))
	(SETQ SAYAC_01 0)
        (WHILE (= CIZGI_UST NIL)
          (SETQ SAYAC_01 (+ SAYAC_01 60))
          (SETQ CIZGI_UST (SSGET "_F" (LIST REF_NOK2 (LIST (CAR REF_NOK2) (+ (CADR REF_NOK2) SAYAC_01) 0.0)) (LIST (CONS 0 "LINE") (CONS 8 "DETAIL3"))))  
        );WHILE
	(SETQ NOK1 (MAPCAR '+ '(0.0 -10.0 0.0)(CDR(ASSOC 10(ENTGET(SSNAME CIZGI_ALT 0))))))
	(SETQ NOK2 (LIST (CAR(CDR(ASSOC 11(ENTGET(SSNAME CIZGI_ALT 0))))) (+(CADR(CDR(ASSOC 11(ENTGET(SSNAME CIZGI_UST 0)))))10.0)0.0))
	(IF (/= (SSGET "_C" NOK1 NOK2 (LIST (CONS 0 "LINE")(CONS 8 "DETAIL2"))) NIL)
	  (PROGN
	    (SETQ DETAIL2 (SSGET "_C" NOK1 NOK2 (LIST (CONS 0 "LINE")(CONS 8 "DETAIL2"))))
	    (SETQ DETAIL2_A (SSLENGTH DETAIL2))
	    (SETQ SAYAC_02 0)
	    (REPEAT DETAIL2_A
	      (ENTMOD (SUBST (CONS 8 "I.DONATI OKU (BEYKENT)") (CONS 8(CDR(ASSOC 8(ENTGET(SSNAME DETAIL2 SAYAC_02)))))(ENTGET (SSNAME DETAIL2 SAYAC_02))))
	      (SETQ SAYAC_02 (1+ SAYAC_02))
	    );REPEAT
	  );PROGN
	);IF
	(ENTMOD (SUBST (CONS 10 (MAPCAR '+ '(25.0 0.0 0.0)(CDR(ASSOC 10(ENTGET(SSNAME DETAIL4 SAYAC)))))) (CONS 10 (CDR(ASSOC 10(ENTGET(SSNAME DETAIL4 SAYAC))))) (ENTGET (SSNAME DETAIL4 SAYAC))))
	(SETQ SAYAC (1+ SAYAC))
      );REPEAT
      (COMMAND-S "_LAYER" "S" "I.DONATI OKU (BEYKENT)" "C" 160 "I.DONATI OKU (BEYKENT)" "LW" 0.2 "I.DONATI OKU (BEYKENT)" "")
      (COMMAND-S "_LAYER" "S" "KESIT ISMI (BEYKENT)" "C" 6 "KESIT ISMI (BEYKENT)" "LW" 0.2 "KESIT ISMI (BEYKENT)" "")
    );PROGN
  );IF
  ;DONATI OKLARI VE KESIT YAZISI
  ;DONATI OKLARI
  (IF (/= (SSGET "X" (LIST (CONS 0 "TEXT")(CONS 1 "*ƒ*")(CONS 8 "DETAIL2"))) NIL)
    (PROGN
      (SETQ DETAIL2 (SSGET "X" (LIST (CONS 0 "TEXT")(CONS 1 "*ƒ*")(CONS 8 "DETAIL2"))))
      (SETQ DETAIL2_A (SSLENGTH DETAIL2))
      (SETQ SAYAC 0)
      (REPEAT DETAIL2_A
	(SETQ REF_NOK1 (MAPCAR '+ '(5.0 -5.0 0.0)(CDR(ASSOC 10(ENTGET(SSNAME DETAIL2 SAYAC))))))
	(SETQ REF_NOK2 (MAPCAR '+ '(-220.0 5.0 0.0)(CDR(ASSOC 10(ENTGET(SSNAME DETAIL2 SAYAC))))))	
	(IF (/= (SSGET "_W" REF_NOK2 REF_NOK1 (LIST (CONS 0 "LINE")(CONS 8 "DETAIL2"))) NIL)
	  (PROGN
	    (SETQ DETAIL2K (SSGET "_W" REF_NOK2 REF_NOK1 (LIST (CONS 0 "LINE")(CONS 8 "DETAIL2"))))
	    (SETQ DETAIL2K_A (SSLENGTH DETAIL2K))
	    (SETQ SAYAC_03 0)
	    (REPEAT DETAIL2K_A
	      (ENTMOD (SUBST (CONS 8 "I.DONATI OKU (BEYKENT)") (CONS 8(CDR(ASSOC 8(ENTGET(SSNAME DETAIL2K SAYAC_03)))))(ENTGET (SSNAME DETAIL2K SAYAC_03))))
	      (SETQ SAYAC_03 (1+ SAYAC_03))
	    );REPEAT
	  );PROGN
	);IF
	(SETQ SAYAC (1+ SAYAC))
      );REPEAT
      (COMMAND-S "_LAYER" "S" "I.DONATI OKU (BEYKENT)" "C" 160 "I.DONATI OKU (BEYKENT)" "LW" 0.2 "I.DONATI OKU (BEYKENT)" "")
    );PROGN
  );IF
  ;DONATI OKLARI
  ;DONATI OKLARI
  (IF (/= (SSGET "X" (LIST (CONS 0 "LINE")(CONS -4 "<OR")(CONS 8 "REBAR2")(CONS 8 "REBAR_DET2")(CONS -4 "OR>"))) NIL)
    (PROGN
      (SETQ REBAR2 (SSGET "X" (LIST (CONS 0 "LINE")(CONS -4 "<OR")(CONS 8 "REBAR2")(CONS 8 "REBAR_DET2")(CONS -4 "OR>"))))
      (SETQ REBAR2_A (SSLENGTH REBAR2))
      (SETQ SAYAC 0)
      (REPEAT REBAR2_A
	(ENTMOD (SUBST (CONS 8 "I.DONATI OKU (BEYKENT)") (CONS 8(CDR(ASSOC 8(ENTGET(SSNAME REBAR2 SAYAC))))) (ENTGET (SSNAME REBAR2 SAYAC))))
	(SETQ SAYAC (1+ SAYAC))
      );REPEAT
      (COMMAND-S "_LAYER" "S" "I.DONATI OKU (BEYKENT)" "C" 160 "I.DONATI OKU (BEYKENT)" "LW" 0.2 "I.DONATI OKU (BEYKENT)" "")
    );PROGN
  );IF
  ;DONATI OKLARI
  ;KESIM CIZGISI
  (IF (/= (SSGET "X" (LIST (CONS 0 "LINE") (CONS 8 "BEAM2"))) NIL)
    (PROGN
      (SETQ BEAM2 (SSGET "X" (LIST (CONS 0 "LINE") (CONS 8 "BEAM2"))))
      (SETQ BEAM2_A (SSLENGTH BEAM2))
      (SETQ SAYAC 0)
      (REPEAT BEAM2_A
	(ENTMOD (SUBST (CONS 8 "KESIT SINIRI (BEYKENT)") (CONS 8 "BEAM2") (ENTGET (SSNAME BEAM2 SAYAC))))
	(SETQ SAYAC (1+ SAYAC))
      );REPEAT
      (COMMAND-S "_LAYER" "S" "KESIT SINIRI (BEYKENT)" "C" 241 "KESIT SINIRI (BEYKENT)" "LW" 0.2 "KESIT SINIRI (BEYKENT)" "LT" "DASHED" "KESIT SINIRI (BEYKENT)" "")
    );PROGN
  );IF
  ;KESIM CIZGISI
  ;OLCU CIZGISI
  (IF (/= (SSGET "X" (LIST (CONS 0 "LINE")(CONS -4 "<OR")(CONS 8 "DIM_LAY")(CONS 8 "DETAIL2")(CONS -4 "OR>"))) NIL)
    (PROGN
      (SETQ DIM_LAY (SSGET "X" (LIST (CONS 0 "LINE")(CONS -4 "<OR")(CONS 8 "DIM_LAY")(CONS 8 "DETAIL2")(CONS -4 "OR>"))))
      (SETQ DIM_LAY_A (SSLENGTH DIM_LAY))
      (SETQ SAYAC 0)
      (REPEAT DIM_LAY_A
	(ENTMOD (SUBST (CONS 8 "OLCU (BEYKENT)")(CONS 8(CDR(ASSOC 8(ENTGET(SSNAME DIM_LAY SAYAC)))))(ENTGET (SSNAME DIM_LAY SAYAC))))
	(SETQ SAYAC (1+ SAYAC))
      );REPEAT
      (COMMAND-S "_LAYER" "S" "OLCU (BEYKENT)" "C" 14 "OLCU (BEYKENT)" "LW" 0.2 "OLCU (BEYKENT)" "")
    );PROGN
  );IF
  ;OLCU CIZGISI
  ;DONATI YAZISI
  (IF (/= (SSGET "X" (LIST (CONS 0 "TEXT")(CONS -4 "<OR")(CONS 1 "*ƒ*")(CONS 1 "*ø*")(CONS -4 "OR>"))) NIL)
    (PROGN
      (SETQ REBAR3 (SSGET "X" (LIST (CONS 0 "TEXT")(CONS -4 "<OR")(CONS 1 "*ƒ*")(CONS 1 "*ø*")(CONS -4 "OR>"))))
      (SETQ REBAR3_A (SSLENGTH REBAR3))
      (SETQ SAYAC 0)
      (REPEAT REBAR3_A
	(ENTMOD (SUBST (CONS 8 "DONATI YAZISI (BEYKENT)")(CONS 8(CDR(ASSOC 8(ENTGET(SSNAME REBAR3 SAYAC)))))(ENTGET (SSNAME REBAR3 SAYAC))))
	(ENTMOD (SUBST (CONS 7 "YAZI (BEYKENT)") (CONS 7(CDR(ASSOC 7(ENTGET(SSNAME REBAR3 SAYAC))))) (ENTGET (SSNAME REBAR3 SAYAC))))
	(ENTMOD (SUBST (CONS 1 (VL-STRING-RIGHT-TRIM "ÿ" (CDR (ASSOC 1 (ENTGET (SSNAME REBAR3 SAYAC)))))) (CONS 1 (CDR (ASSOC 1 (ENTGET (SSNAME REBAR3 SAYAC))))) (ENTGET (SSNAME REBAR3 SAYAC))))
	(ENTMOD (SUBST (CONS 1 (VL-STRING-SUBST "ø" "ƒ" (CDR (ASSOC 1 (ENTGET (SSNAME REBAR3 SAYAC)))))) (CONS 1 (CDR (ASSOC 1 (ENTGET (SSNAME REBAR3 SAYAC))))) (ENTGET (SSNAME REBAR3 SAYAC))))
	(ENTMOD (SUBST (CONS 40 10) (CONS 40(CDR(ASSOC 40(ENTGET(SSNAME REBAR3 SAYAC))))) (ENTGET (SSNAME REBAR3 SAYAC))))
	(IF (/= (WCMATCH (CDR (ASSOC 1 (ENTGET (SSNAME REBAR3 SAYAC)))) "*etr.*") NIL) (ENTMOD (SUBST (CONS 10 (MAPCAR '+ '(45.0 0.0 0.0)(CDR(ASSOC 10(ENTGET(SSNAME REBAR3 SAYAC)))))) (CONS 10(CDR(ASSOC 10(ENTGET(SSNAME REBAR3 SAYAC))))) (ENTGET (SSNAME REBAR3 SAYAC)))))
	(SETQ SAYAC (1+ SAYAC))
      );REPEAT
      (COMMAND-S "_LAYER" "S" "DONATI YAZISI (BEYKENT)" "C" 3 "DONATI YAZISI (BEYKENT)" "LW" 0.2 "DONATI YAZISI (BEYKENT)" "")
    );PROGN
  );IF
  ;DONATI YAZISI
  ;OLCU YAZISI
  (IF (/= (SSGET "X" (LIST (CONS 0 "TEXT")(CONS -4 "<OR")(CONS 8 "DIM_LAY")(CONS 8 "DETAIL2")(CONS 8 "REBAR2")(CONS 8 "REBAR_DET2")(CONS -4 "OR>"))) NIL)
    (PROGN
      (SETQ DIM_LAY (SSGET "X" (LIST (CONS 0 "TEXT")(CONS -4 "<OR")(CONS 8 "DIM_LAY")(CONS 8 "DETAIL2")(CONS 8 "REBAR2")(CONS 8 "REBAR_DET2")(CONS -4 "OR>"))))
      (SETQ DIM_LAY_A (SSLENGTH DIM_LAY))
      (SETQ SAYAC 0)
      (REPEAT DIM_LAY_A
	(ENTMOD (SUBST (CONS 8 "OLCU YAZISI (BEYKENT)") (CONS 8(CDR(ASSOC 8(ENTGET(SSNAME DIM_LAY SAYAC))))) (ENTGET (SSNAME DIM_LAY SAYAC))))
	(ENTMOD (SUBST (CONS 40 10) (CONS 40(CDR(ASSOC 40(ENTGET(SSNAME DIM_LAY SAYAC))))) (ENTGET (SSNAME DIM_LAY SAYAC))))
	(ENTMOD (SUBST (CONS 7 "OLCU (BEYKENT)") (CONS 7(CDR(ASSOC 7(ENTGET(SSNAME DIM_LAY SAYAC))))) (ENTGET (SSNAME DIM_LAY SAYAC))))
	(SETQ SAYAC (1+ SAYAC))
      );REPEAT
      (COMMAND-S "_LAYER" "S" "OLCU YAZISI (BEYKENT)" "C" 7 "OLCU YAZISI (BEYKENT)" "LW" 0.2 "OLCU YAZISI (BEYKENT)" "")
    );PROGN
  );IF
  ;OLCU YAZISI
  ;KESIT IMI
  (IF (/= (SSGET "X" (LIST (CONS 0 "TEXT") (CONS 40 20) (CONS 8 "DETAIL4"))) NIL)
    (PROGN
      (SETQ DETAIL4 (SSGET "X" (LIST (CONS 0 "TEXT") (CONS 40 20) (CONS 8 "DETAIL4"))))
      (SETQ DETAIL4_A (SSLENGTH DETAIL4))
      (SETQ SAYAC 0)
      (REPEAT DETAIL4_A
	(ENTMOD (SUBST (CONS 8 "KESIT ISMI (BEYKENT)") (CONS 8(CDR(ASSOC 8(ENTGET(SSNAME DETAIL4 SAYAC))))) (ENTGET (SSNAME DETAIL4 SAYAC))))
	(ENTMOD (SUBST (CONS 40 12.5) (CONS 40(CDR(ASSOC 40(ENTGET(SSNAME DETAIL4 SAYAC))))) (ENTGET (SSNAME DETAIL4 SAYAC))))
	(ENTMOD (SUBST (CONS 50 (/ PI 2)) (CONS 50(CDR(ASSOC 50(ENTGET(SSNAME DETAIL4 SAYAC))))) (ENTGET (SSNAME DETAIL4 SAYAC))))
	(ENTMOD (SUBST (CONS 7 "YAZI (BEYKENT)") (CONS 7(CDR(ASSOC 7(ENTGET(SSNAME DETAIL4 SAYAC))))) (ENTGET (SSNAME DETAIL4 SAYAC))))
	(COMMAND-S "_ERASE" (SSGET "_W" (MAPCAR '+ '(0.0 70.0 0.0) (CDR (ASSOC 10 (ENTGET (SSNAME DETAIL4 SAYAC))))) (MAPCAR '+ '(50.0 -50.0 0.0) (CDR (ASSOC 10 (ENTGET (SSNAME DETAIL4 SAYAC))))) (LIST (CONS 0 "LINE") (CONS 8 "DETAIL4"))) "" )
	(SETQ SAYAC (1+ SAYAC))
      );REPEAT
      (COMMAND-S "_LAYER" "S" "KESIT ISMI (BEYKENT)" "C" 6 "KESIT ISMI (BEYKENT)" "LW" 0.2 "KESIT ISMI (BEYKENT)" "")
    );PROGN
  );IF
  ;KESIT IMI
  ;DONATI
  (IF (/= (SSGET "X" (LIST (CONS -4 "<OR")(CONS 0 "LINE")(CONS 0 "CIRCLE")(CONS -4 "OR>")(CONS -4 "<OR")(CONS 8 "REBAR")(CONS 8 "DETAIL4")(CONS 8 "REBAR_DET4")(CONS 8 "BEAM4")(CONS -4 "OR>"))) NIL)
    (PROGN
      (SETQ REBAR (SSGET "X" (LIST (CONS -4 "<OR")(CONS 0 "LINE")(CONS 0 "CIRCLE")(CONS -4 "OR>")(CONS -4 "<OR")(CONS 8 "REBAR")(CONS 8 "DETAIL4")(CONS 8 "REBAR_DET4")(CONS 8 "BEAM4")(CONS -4 "OR>"))))
      (SETQ REBAR_A (SSLENGTH REBAR))
      (SETQ SAYAC 0)
      (REPEAT REBAR_A
	(ENTMOD (SUBST (CONS 8 "DONATI (BEYKENT)") (CONS 8(CDR(ASSOC 8(ENTGET(SSNAME REBAR SAYAC))))) (ENTGET (SSNAME REBAR SAYAC))))
	(SETQ SAYAC (1+ SAYAC))
      );REPEAT
      (COMMAND-S "_LAYER" "S" "DONATI (BEYKENT)" "C" 4 "DONATI (BEYKENT)" "LW" 0.35 "DONATI (BEYKENT)" "")
    );PROGN
  );IF
  ;DONATI
  ;KESIT KIRIS YAZISI
  (IF (/= (SSGET "X" (LIST (CONS 0 "TEXT") (CONS 40 15) (CONS 8 "DETAIL3"))) NIL)
    (PROGN
      (SETQ DETAIL3 (SSGET "X" (LIST (CONS 0 "TEXT") (CONS 40 15) (CONS 8 "DETAIL3"))))
      (SETQ DETAIL3_A (SSLENGTH DETAIL3))
      (SETQ SAYAC 0)
      (REPEAT DETAIL3_A
	(ENTMOD (SUBST (CONS 8 "KIRIS ISMI (BEYKENT)") (CONS 8(CDR(ASSOC 8(ENTGET(SSNAME DETAIL3 SAYAC))))) (ENTGET (SSNAME DETAIL3 SAYAC))))
	(ENTMOD (SUBST (CONS 40 12.5) (CONS 40(CDR(ASSOC 40(ENTGET(SSNAME DETAIL3 SAYAC))))) (ENTGET (SSNAME DETAIL3 SAYAC))))
	(ENTMOD (SUBST (CONS 7 "YAZI (BEYKENT)") (CONS 7(CDR(ASSOC 7(ENTGET(SSNAME DETAIL3 SAYAC))))) (ENTGET (SSNAME DETAIL3 SAYAC))))
	(ENTMOD (SUBST (CONS 10 (MAPCAR '+ '(25.0 7.5 0.0)(CDR(ASSOC 10(ENTGET(SSNAME DETAIL3 SAYAC)))))) (CONS 10 (CDR(ASSOC 10(ENTGET(SSNAME DETAIL3 SAYAC))))) (ENTGET (SSNAME DETAIL3 SAYAC))))
	(SETQ SAYAC (1+ SAYAC))
      );REPEAT
      (COMMAND-S "_LAYER" "S" "KIRIS ISMI (BEYKENT)" "C" 40 "KIRIS ISMI (BEYKENT)" "LW" 0.2 "KIRIS ISMI (BEYKENT)" "")
    );PROGN
  );IF
  ;KESIT KIRIS YAZISI
  ;KIRIS CIZGISI
  (IF (/= (SSGET "X" (LIST (CONS 0 "LINE") (CONS 8 "DETAIL3"))) NIL)
    (PROGN
      (SETQ DETAIL3 (SSGET "X" (LIST (CONS 0 "LINE") (CONS 8 "DETAIL3"))))
      (SETQ DETAIL3_A (SSLENGTH DETAIL3))
      (SETQ SAYAC 0)
      (REPEAT DETAIL3_A
	(ENTMOD (SUBST (CONS 8 "KIRIS (BEYKENT)") (CONS 8(CDR(ASSOC 8(ENTGET(SSNAME DETAIL3 SAYAC))))) (ENTGET (SSNAME DETAIL3 SAYAC))))
	(SETQ SAYAC (1+ SAYAC))
      );REPEAT
      (COMMAND-S "_LAYER" "S" "KIRIS (BEYKENT)" "C" 2 "KIRIS (BEYKENT)" "LW" 0.3 "KIRIS (BEYKENT)" "")
    );PROGN
  );IF
  ;KIRIS CIZGISI
  ;DONATI TARAMASI
  (IF (/= (SSGET "X" (LIST (CONS 0 "CIRCLE") (CONS 8 "DONATI (BEYKENT)"))) NIL)
    (PROGN
      (SETQ DONATI (SSGET "X" (LIST (CONS 0 "CIRCLE") (CONS 8 "DONATI (BEYKENT)"))))
      (SETQ DONATI_A (SSLENGTH DONATI))
      (SETQ SAYAC 0)
      (REPEAT DONATI_A
	(SETQ DONATI_NOKTA_YERI (CDR (ASSOC 10 (ENTGET (SSNAME DONATI SAYAC)))))
	(COMMAND-S "_.INSERT" "DONATI" DONATI_NOKTA_YERI 1 1 0)
	(COMMAND-S "_EXPLODE" (ENTLAST))
	(SETQ SAYAC (1+ SAYAC))
      );REPEAT
      (COMMAND-S "_ERASE" DONATI "")
    );PROGN
  );IF
  ;DONATI TARAMASI
  ;KESIT SIMGESI
  (IF (/= (SSGET "X" (LIST (CONS 0 "TEXT") (CONS 40 12.5) (CONS 8 "KESIT ISMI (BEYKENT)"))) NIL)
    (PROGN
      (SETQ KESIT_ADI (SSGET "X" (LIST (CONS 0 "TEXT") (CONS 40 12.5) (CONS 8 "KESIT ISMI (BEYKENT)"))))
      (SETQ KESIT_ADI_A (SSLENGTH KESIT_ADI))
      (SETQ SAYAC 0)
      (REPEAT KESIT_ADI_A
	(SETQ KESIT_NOKTA_YERI (CDR (ASSOC 10 (ENTGET (SSNAME KESIT_ADI SAYAC)))))
	(COMMAND-S "_.INSERT" "KES_DET" KESIT_NOKTA_YERI 1 1 0)
	(COMMAND-S "_EXPLODE" (ENTLAST))
	(SETQ SAYAC (1+ SAYAC))
      );REPEAT
    );PROGN
  );IF
  ;KESIT SIMGESI
  ;KOT SIMGESI
  (IF (/= (SSGET "X" (LIST (CONS 0 "TEXT") (CONS 40 10) (CONS 8 "KOT YAZI (BEYKENT)"))) NIL)
    (PROGN
      (SETQ KOT_ADI (SSGET "X" (LIST (CONS 0 "TEXT") (CONS 40 10) (CONS 8 "KOT YAZI (BEYKENT)"))))
      (SETQ KOT_ADI_A (SSLENGTH KOT_ADI))
      (SETQ SAYAC 0)
      (REPEAT KOT_ADI_A
	(SETQ KOT_NOKTA_YERI (CDR (ASSOC 10 (ENTGET (SSNAME KOT_ADI SAYAC)))))
	(COMMAND-S "_.INSERT" "KOT" KOT_NOKTA_YERI 1 1 0)
	(COMMAND-S "_EXPLODE" (ENTLAST))
	(SETQ SAYAC (1+ SAYAC))
      );REPEAT
    );PROGN
  );IF
  ;KOT SIMGESI  
  (SETVAR "OSMODE" CURRENT_OSM)
  (COMMAND "UNDO" "E")
  (PRINC)  
);DEFUN
